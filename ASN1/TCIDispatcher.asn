--<OSS.PDU TCI-Dispatcher.TCIMsg>--

/* Copyright 2023 OmniAir Consortium Inc. All rights reserved.
   Licensed http://www.apache.org/licenses/LICENSE-2.0 (the "License");
   You may not use this file except in compliance with the License.  */
   
TCI-Dispatcher
DEFINITIONS AUTOMATIC TAGS ::=
BEGIN

IMPORTS

TCIPROXYCV2X        FROM TCI-CV2X-PROXY
TCI16093DSRC        FROM TCI-16093-DSRC
TCI16093PC5         FROM TCI-16093-PC5
TCI16094            FROM TCI-16094
TCI80211            FROM TCI-80211
TCI29451            FROM TCI-29451
TCI31611            FROM TCI-31611
TCISutControl       FROM TCI-SutControl
Time64              FROM TCI-CommonTypes
TCICuckoo           FROM TCI-Cuckoo
TCIUseCaseControl   FROM TCI-UseCaseControl
;

TCIMsg ::= SEQUENCE{
    version     INTEGER {currentVersion(4)} (1..127),  -- current protocol version 3
    time        Time64,                                -- UTC time stamp with milliseconds, GPS synchronized
    frame       Frame,                                 -- protocol layer
    ...
    }

Frame ::=CHOICE {
    d16093dsrc [1] TCI16093DSRC,
    --d16092   [2] TCI16092, module is redundant with TCI16093
    d80211     [3] TCI80211,
    d16094     [4] TCI16094,
    d29451     [5] TCI29451,
    sutCtrl    [6] TCISutControl,
    ...,
    d16093cv2x [7] TCI16093PC5,
    d31611     [8] TCI31611,
    proxyCv2x  [16] TCIPROXYCV2X,
    useCuckoo  [17] TCICuckoo, -- Cuckoo module injects simulated drives & events to test ITS apps
    useCaseControl [18] TCIUseCaseControl -- module that configures the production of UCAM use-case alerts
}


END
